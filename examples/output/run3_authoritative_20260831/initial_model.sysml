package AutonomousDrone {    item def ValidWaypointModificationCommand;
    item def SteadyCruiseConditionMet;
    item def SinglePropulsionUnitFailure;
    item def PowerOn;
    item def PayloadReleaseCommand;
    item def NonCriticalContingencyDetected;
    item def MissionCommandReceived;
    item def MaxPayloadCruiseConditionMet;
    item def HeadwindConditionMet;
    item def DeliveryCoordinateConditionSatisfied;
    item def CriticalPropulsionSubsystemFailure;
    item def CollisionThreatDetected;
    item def AutomatedLandingCompleted;
    item def ArmingCommand;
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    
    

    private import MeasurementReferences::*;
    private import ScalarValues::*;
    alias deg for SI::degree;
    alias m_s for SI::'m/s';
    attribute percent : DimensionOneUnit {
        :>> unitConversion : ConversionByConvention {
            :>> referenceUnit = one;
            :>> conversionFactor = 0.01;
        }
    }
    
    
    
    
    
    
    
    
    
    
    
    
    
    
    
    
    
    
    
    
    
    
    
    
    
    
    
    

    private import ISQ::*;
    private import SI::*;
    
    
    
    
    
    
    
    
    
    
    
    
    
    
    
    
    
    
    
    
    
    
    
    
    
    
    
    


    // Attribute definitions for semantic bindings
    attribute def LengthValue :> Real;
    attribute def DimensionOneValue :> Real;
    attribute def AngularMeasureValue :> Real;
    attribute def DurationValue :> Real;
    attribute def SpeedValue :> Real;
    attribute def MassValue :> Real;

    // Item definitions for semantic bindings
    item def ObstacleAvoidanceSeparationData {
        attribute airframeObstacleSeparation : LengthValue;
    }
    
    item def PayloadThrottleMarginData {
        attribute hoverThrottleMargin : DimensionOneValue;
    }
    
    item def AttitudeDeviationsData {
        attribute rollPitchAttitudeDeviations : AngularMeasureValue;
    }
    
    item def FlightDurationData {
        attribute flight : DurationValue;
    }
    
    item def CruiseAirspeedData {
        attribute airspeed : SpeedValue;
    }
    
    item def ForwardGroundSpeedData {
        attribute speed : SpeedValue;
    }
    
    item def OperationalRangeData {
        attribute range : LengthValue;
    }
    
    item def FlightAltitudeData {
        attribute altitude : LengthValue;
    }
    
    item def PayloadMassPropertiesData {
        attribute takeOffMassPayloadBattery : MassValue;
    }

    // Port definitions for semantic bindings
    port def ObstacleAvoidanceSeparationPort {
        inout item payload : ObstacleAvoidanceSeparationData;
    }
    
    port def PayloadThrottleMarginPort {
        inout item payload : PayloadThrottleMarginData;
    }
    
    port def AttitudeDeviationsPort {
        inout item payload : AttitudeDeviationsData;
    }
    
    port def FlightDurationPort {
        inout item payload : FlightDurationData;
    }
    
    port def CruiseAirspeedPort {
        inout item payload : CruiseAirspeedData;
    }
    
    port def ForwardGroundSpeedPort {
        inout item payload : ForwardGroundSpeedData;
    }
    
    port def OperationalRangePort {
        inout item payload : OperationalRangeData;
    }
    
    port def FlightAltitudePort {
        inout item payload : FlightAltitudeData;
    }
    
    port def PayloadMassPropertiesPort {
        inout item payload : PayloadMassPropertiesData;
    }

    // Item definitions for other ports
    item def ContingencyReturnLandingCmdData;
    item def WaypointNavigateCommandData;
    
    item def TelemetryDataLinkData {
        doc /* MAVLink v2.0 protocol over AES-256 encrypted RF channel */
    }
    
    item def DeliveryPayloadCmdData;
    item def PropulsionCmdData;
    item def WaypointModificationData;
    item def LandingHealthReportData;
    item def OverrideCmdData;
    item def SensorStatusData;
    
    item def GnssCorrectionsData {
        doc /* RTCM 10403.3 standard */
    }
    
    item def UplinkCommStatusData;
    item def RfLinkData;
    
    item def RemoteIdData {
        doc /* ASTM F3411-22 standard */
    }
    
    item def CommStatusData;
    item def AbortLockCmdData;
    item def BatteryStatusData;
    item def RecoveryCmdData;
    item def PropulsionStatusData;

    // Port definitions for other ports
    port def ContingencyReturnLandingCmdPort {
        inout item payload : ContingencyReturnLandingCmdData;
    }
    
    port def WaypointNavigateCommandPort {
        inout item payload : WaypointNavigateCommandData;
    }
    
    port def TelemetryDataLinkPort {
        inout item payload : TelemetryDataLinkData;
    }
    
    port def DeliveryPayloadCmdPort {
        inout item payload : DeliveryPayloadCmdData;
    }
    
    port def PropulsionCmdPort {
        inout item payload : PropulsionCmdData;
    }
    
    port def WaypointModificationPort {
        inout item payload : WaypointModificationData;
    }
    
    port def LandingHealthReportPort {
        inout item payload : LandingHealthReportData;
    }
    
    port def OverrideCmdPort {
        inout item payload : OverrideCmdData;
    }
    
    port def SensorStatusPort {
        inout item payload : SensorStatusData;
    }
    
    port def GnssCorrectionsPort {
        inout item payload : GnssCorrectionsData;
    }
    
    port def UplinkCommStatusPort {
        inout item payload : UplinkCommStatusData;
    }
    
    port def RfLinkPort {
        inout item payload : RfLinkData;
    }
    
    port def RemoteIdPort {
        inout item payload : RemoteIdData;
    }
    
    port def CommStatusPort {
        inout item payload : CommStatusData;
    }
    
    port def AbortLockCmdPort {
        inout item payload : AbortLockCmdData;
    }
    
    port def BatteryStatusPort {
        inout item payload : BatteryStatusData;
    }
    
    port def RecoveryCmdPort {
        inout item payload : RecoveryCmdData;
    }
    
    port def PropulsionStatusPort {
        inout item payload : PropulsionStatusData;
    }

    // Planned event symbols
    
    
    
    
    
    
    
    
    
    
    
    
    
    

    // Requirements
    requirement def REQ_FUNC_001 { doc /* The system shall autonomously navigate to designated GPS waypoints with a circular error probable (CEP) of less than 1.0 metre. [V: hardware-in-the-loop / field survey] */ }
    requirement def REQ_FUNC_002 { doc /* When approaching a stationary collision threat directly ahead within the forward sensor field of view at a closing speed no greater than 1.5 m/s, the system shall execute an avoidance manoeuvre following threat detection no later than 15 metres, maintaining an airframe-to-obstacle separation of at least 5 metres. */ }
    requirement def REQ_FUNC_003 { doc /* The system shall transport payloads with a gross mass of up to 1.5 kg while maintaining a hover throttle margin of at least 30 percent and roll and pitch RMS within 1.0 degree. */ }
    requirement def REQ_FUNC_004 { doc /* The system shall maintain a continuously encrypted bidirectional data link with the GCS for telemetry upload and mission command download throughout the operational flight envelope. */ }
    requirement def REQ_FUNC_005 { doc /* The system shall release the payload when the current geographic position is within 1.0 metre of the designated delivery waypoint and no delivery-abort condition is active. */ }
    requirement def REQ_FUNC_006 { doc /* The system shall incorporate a revised waypoint sequence into the active flight plan within 1.0 second of receiving a valid waypoint-modification command from the GCS. */ }
    requirement def REQ_FUNC_007 { doc /* The system shall autonomously execute a return-to-base trajectory upon detection of a non-critical contingency (GCS link loss, geofence breach, or battery state-of-charge at the return threshold) that does not require immediate landing. */ }
    requirement def REQ_FUNC_008 { doc /* The AutonomousDrone shall transmit a post-flight system health report to the GCS within 5.0 seconds of completing an automated landing. */ }
    requirement def REQ_PERF_001 { doc /* The system shall maintain roll and pitch attitude deviations within 0.5 degree RMS during steady cruise flight at all authorised speeds. [V: Gazebo attitude logging / HIL] */ }
    requirement def REQ_PERF_002 { doc /* The system shall sustain flight for a minimum of 25 minutes when carrying the maximum rated payload at nominal cruise speed. */ }
    requirement def REQ_PERF_003 { doc /* The system shall achieve a cruise airspeed of at least 18 m/s in nil-wind, level-flight conditions. */ }
    requirement def REQ_PERF_004 { doc /* The system shall maintain a minimum forward ground speed of 2 m/s when operating in sustained headwinds of up to 15 m/s. */ }
    requirement def REQ_PERF_005 { doc /* The mechanical payload release actuation shall complete within 2.0 seconds from the moment the delivery coordinate condition is satisfied. */ }
    requirement def REQ_PERF_006 { doc /* The system shall achieve an operational range of at least 5 km on a single charge at nominal cruise speed with the maximum rated payload. */ }
    requirement def REQ_SAFE_001 { doc /* The system shall initiate an autonomous return-to-base sequence when the battery state-of-charge reaches 25%, unless a higher-priority safety response is already in progress. */ }
    requirement def REQ_SAFE_002 { doc /* The system shall perform a controlled descent to the nearest safe landing area when the battery state-of-charge falls below 15%, superseding any lower-priority contingency response. */ }
    requirement def REQ_SAFE_003 { doc /* The system shall perform an autonomous safe landing at the current position when the GCS uplink has been absent for more than 10 consecutive seconds. */ }
    requirement def REQ_SAFE_004 { doc /* The system shall not transition to the armed or airborne state if any onboard sensor reports a failure during the power-on self-test sequence. */ }
    requirement def REQ_SAFE_005 { doc /* The system shall deploy the ballistic recovery parachute within 0.5 seconds of detecting a critical propulsion subsystem failure during flight, taking precedence over all other safety responses. */ }
    requirement def REQ_SAFE_006 { doc /* The system shall maintain the payload in the mechanically locked state whenever a delivery-abort condition is active, regardless of geographic proximity to the delivery waypoint. */ }
    requirement def REQ_SAFE_007 { doc /* The system shall maintain controlled flight following the failure of a single propulsion unit (one motor inoperative). */ }
    requirement def REQ_SAFE_008 { doc /* The payload-release actuator shall default to the mechanically locked state upon power-on, before any arming or flight authorisation. */ }
    requirement def REQ_INTF_001 { doc /* The system shall exchange telemetry and mission commands with the GCS using the MAVLink v2.0 protocol over an AES-256 encrypted RF channel. */ }
    requirement def REQ_INTF_002 { doc /* The system shall receive and apply differential GNSS corrections formatted according to the RTCM 10403.3 standard to achieve sub-metre positioning accuracy. [V: hardware-in-the-loop / RTK bench] */ }
    requirement def REQ_INTF_003 { doc /* The system shall broadcast remote identification and real-time spatial positioning data in accordance with the ASTM F3411-22 standard. [V: inspection / conformance test] */ }
    requirement def REQ_CONS_001 { doc /* The system shall not exceed a flight altitude of 120 metres above ground level at any point during normal operations. */ }
    requirement def REQ_CONS_002 { doc /* All airframe and electronic enclosures exposed to the external environment shall meet a minimum IP54 ingress-protection rating. [V: inspection / ingress test] */ }
    requirement def REQ_CONS_003 { doc /* The system maximum take-off mass, including payload and battery, shall not exceed 8.0 kg. */ }
    requirement def REQ_CONS_004 { doc /* The system shall comply with EASA UAS Category C operational regulations. [V: inspection / regulatory audit] */ }

    // Part Definitions
    part def FlightController {
        in port obstacleAvoidanceSeparation : ObstacleAvoidanceSeparationPort;
        in port payloadThrottleMargin : PayloadThrottleMarginPort;
        in port attitudeDeviations : AttitudeDeviationsPort;
        in port flightDuration : FlightDurationPort;
        in port cruiseAirspeed : CruiseAirspeedPort;
        in port forwardGroundSpeed : ForwardGroundSpeedPort;
        in port operationalRange : OperationalRangePort;
        in port flightAltitude : FlightAltitudePort;
        in port payloadMassProperties : PayloadMassPropertiesPort;
        in port contingencyReturnLandingCmd : ContingencyReturnLandingCmdPort;
        in port waypointNavigateCommand : WaypointNavigateCommandPort;
        out port telemetryDataLink : TelemetryDataLinkPort;
        out port deliveryPayloadCmd : DeliveryPayloadCmdPort;
        out port propulsionCmd : PropulsionCmdPort;
        in port waypointModification : WaypointModificationPort;
        out port landingHealthReport : LandingHealthReportPort;
        in port overrideCmd : OverrideCmdPort;

        attribute minObstacleSeparation : LengthValue = 5 [m];
        attribute currentAirframeObstacleSeparation : LengthValue = obstacleAvoidanceSeparation.payload.airframeObstacleSeparation;
        attribute minThrottleMargin : DimensionOneValue = 30 [percent];
        attribute currentHoverThrottleMargin : DimensionOneValue = payloadThrottleMargin.payload.hoverThrottleMargin;
        attribute maxAttitudeDeviations : AngularMeasureValue = 0.5 [deg];
        attribute currentRollPitchAttitudeDeviations : AngularMeasureValue = attitudeDeviations.payload.rollPitchAttitudeDeviations;
        attribute minFlightDuration : DurationValue = 25 [min];
        attribute currentFlightDuration : DurationValue = flightDuration.payload.flight;
        attribute minCruiseAirspeed : SpeedValue = 18 [m_s];
        attribute currentCruiseAirspeed : SpeedValue = cruiseAirspeed.payload.airspeed;
        attribute minForwardGroundSpeed : SpeedValue = 2 [m_s];
        attribute currentForwardGroundSpeed : SpeedValue = forwardGroundSpeed.payload.speed;
        attribute minOperationalRange : LengthValue = 5 [km];
        attribute currentOperationalRange : LengthValue = operationalRange.payload.range;
        attribute maxFlightAltitude : LengthValue = 120 [m];
        attribute currentFlightAltitude : LengthValue = flightAltitude.payload.altitude;
        attribute maxTakeOffMass : MassValue = 8 [kg];
        attribute currentTakeOffMassPayloadBattery : MassValue = payloadMassProperties.payload.takeOffMassPayloadBattery;
        attribute maxWaypointModificationLatency : Real = 1.0 [s];
        attribute measuredWaypointModificationLatency : Real = 0.0 [s];
        attribute maxHealthReportLatency : Real = 5.0 [s];
        attribute measuredHealthReportLatency : Real = 0.0 [s];
        attribute controlFrequency : Real = 100.0 [Hz];

        satisfy requirement REQ_FUNC_001;
        satisfy requirement REQ_FUNC_002;
        satisfy requirement REQ_FUNC_003;
        satisfy requirement REQ_FUNC_006;
        satisfy requirement REQ_FUNC_007;
        satisfy requirement REQ_FUNC_008;
        satisfy requirement REQ_PERF_001;
        satisfy requirement REQ_PERF_003;
        satisfy requirement REQ_PERF_004;
        satisfy requirement REQ_CONS_001;

        // PLAN-CONSTRAINT waypointModificationLatencyConstraint provenance=FROZEN_REQUIREMENT activation=ALWAYS verification=STATE_EXECUTION
        assert constraint waypointModificationLatencyConstraint {
            measuredWaypointModificationLatency <= maxWaypointModificationLatency
        }
        // PLAN-CONSTRAINT healthReportLatencyConstraint provenance=FROZEN_REQUIREMENT activation=ALWAYS verification=STATE_EXECUTION
        assert constraint healthReportLatencyConstraint {
            measuredHealthReportLatency <= maxHealthReportLatency
        }
        // PLAN-CONSTRAINT obstacleSeparationConstraint provenance=FROZEN_REQUIREMENT activation=ALWAYS verification=PARAMETRIC_SWEEP
        assert constraint obstacleSeparationConstraint {
            currentAirframeObstacleSeparation >= minObstacleSeparation
        }
        // PLAN-CONSTRAINT throttleMarginConstraint provenance=FROZEN_REQUIREMENT activation=ALWAYS verification=PARAMETRIC_SWEEP
        assert constraint throttleMarginConstraint {
            currentHoverThrottleMargin >= minThrottleMargin
        }
        // PLAN-CONSTRAINT cruiseAirspeedConstraint provenance=FROZEN_REQUIREMENT activation=ALWAYS verification=PARAMETRIC_SWEEP
        assert constraint cruiseAirspeedConstraint {
            currentCruiseAirspeed >= minCruiseAirspeed
        }
        // PLAN-CONSTRAINT operationalRangeConstraint provenance=FROZEN_REQUIREMENT activation=ALWAYS verification=PARAMETRIC_SWEEP
        // DELEGATED-CONSTRAINT operationalRangeConstraint tier=FORWARD_FLIGHT_FIDELITY reason=mission-end-capability
        // Operational range is a mission-end capability evaluated by forward-flight fidelity, not an invariant.
// PLAN-CONSTRAINT flightAltitudeConstraint provenance=FROZEN_REQUIREMENT activation=ALWAYS verification=PARAMETRIC_SWEEP
        assert constraint flightAltitudeConstraint {
            currentFlightAltitude <= maxFlightAltitude
        }
        // PLAN-CONSTRAINT takeOffMassConstraint provenance=FROZEN_REQUIREMENT activation=ALWAYS verification=PARAMETRIC_SWEEP
        assert constraint takeOffMassConstraint {
            currentTakeOffMassPayloadBattery <= maxTakeOffMass
        }

        action def awaitMission {}
        action def cruiseWithMaxPayload {}
        action def flyInHeadwinds {}
        action def followCurrentWaypoints {}
        action def maintainNominalFlight {}
        action def maintainSteadyCruise {}
        action def monitorCruise {}
        action def monitorFlight {}
        action def monitorHeadwind {}
        action def monitorPath {}
        action def monitorPayloadCruise {}
        action def navigateAvoidanceManoeuvre {}
        action def navigateRevisedWaypointSequence {}
        action def navigateWaypoints {}
        action def reportSystemHealth {}
        action def rtbTrajectory {}

                                                        state def SteadyCruiseBehavior {
            entry; then NotSteadyCruise;

            state NotSteadyCruise {
                do action runNotSteadyCruise : monitorCruise;
            }
            state SteadyCruiseFlight {
                do action runSteadyCruiseFlight : maintainSteadyCruise;
            
            // PLAN-CONSTRAINT attitudeDeviationsConstraint provenance=FROZEN_REQUIREMENT activation=STATE_ACTIVE verification=STATE_EXECUTION reference=SteadyCruiseBehavior::SteadyCruiseFlight
            assert constraint attitudeDeviationsConstraint {
                currentRollPitchAttitudeDeviations <= maxAttitudeDeviations
            }
        }

            transition enterSteadyCruise
                first NotSteadyCruise
                accept SteadyCruiseConditionMet
                then SteadyCruiseFlight;
        }
    
    
    
    
    
    

                                                        state def WaypointManagementBehavior {
            entry; then Idle;

            state Idle {
                do action runIdle : followCurrentWaypoints;
            }
            state UpdatingWaypoints {
                entry action onUpdatingWaypoints : navigateRevisedWaypointSequence;
            }

            transition receiveWaypointModification
                first Idle
                accept ValidWaypointModificationCommand
                then UpdatingWaypoints;
        }
    
    
    
    
    
    

                                                        state def HealthReportingBehavior {
            entry; then Flight;

            state Flight {
                do action runFlight : monitorFlight;
            }
            state ReportingHealth {
                entry action onReportingHealth : reportSystemHealth;
            }

            transition landingCompleted
                first Flight
                accept AutomatedLandingCompleted
                then ReportingHealth;
        }
    
    
    
    
    
    

                                                        state def ContingencyResponseBehavior {
            entry; then NominalFlight;

            state NominalFlight {
                do action runNominalFlight : maintainNominalFlight;
            }
            state ReturnToBase {
                entry action onReturnToBase : rtbTrajectory;
            }

            transition contingencyDetected
                first NominalFlight
                accept NonCriticalContingencyDetected
                then ReturnToBase;
        }
    
    
    
    
    
    

                                                        state def NavigationBehavior {
            entry; then Standby;

            state Standby {
                do action runStandby : awaitMission;
            }
            state Navigating {
                do action runNavigating : navigateWaypoints;
            }

            transition startMission
                first Standby
                accept MissionCommandReceived
                then Navigating;
        }
    
    
    
    
    
    

                                                        state def ObstacleAvoidanceBehavior {
            entry; then ClearPath;

            state ClearPath {
                do action runClearPath : monitorPath;
            }
            state Avoiding {
                entry action onAvoiding : navigateAvoidanceManoeuvre;
            }

            transition threatDetected
                first ClearPath
                accept CollisionThreatDetected
                then Avoiding;
        }
    
    
    
    
    
    

                                                        state def MaxPayloadCruiseBehavior {
            entry; then NotMaxPayloadCruise;

            state NotMaxPayloadCruise {
                do action runNotMaxPayloadCruise : monitorPayloadCruise;
            }
            state NominalCruiseWithMaxPayload {
                do action runNominalCruiseWithMaxPayload : cruiseWithMaxPayload;
            
            // PLAN-CONSTRAINT flightDurationConstraint provenance=FROZEN_REQUIREMENT activation=STATE_ACTIVE verification=STATE_EXECUTION reference=MaxPayloadCruiseBehavior::NominalCruiseWithMaxPayload
            assert constraint flightDurationConstraint {
                currentFlightDuration >= minFlightDuration
            }
        }

            transition enterMaxPayloadCruise
                first NotMaxPayloadCruise
                accept MaxPayloadCruiseConditionMet
                then NominalCruiseWithMaxPayload;
        }
    
    
    
    
    
    

                                                        state def HeadwindFlightBehavior {
            entry; then NotHeadwindFlight;

            state NotHeadwindFlight {
                do action runNotHeadwindFlight : monitorHeadwind;
            }
            state SustainedHeadwinds {
                do action runSustainedHeadwinds : flyInHeadwinds;
            
            // PLAN-CONSTRAINT forwardGroundSpeedConstraint provenance=FROZEN_REQUIREMENT activation=STATE_ACTIVE verification=STATE_EXECUTION reference=HeadwindFlightBehavior::SustainedHeadwinds
            assert constraint forwardGroundSpeedConstraint {
                currentForwardGroundSpeed >= minForwardGroundSpeed
            }
        }

            transition enterHeadwindFlight
                first NotHeadwindFlight
                accept HeadwindConditionMet
                then SustainedHeadwinds;
        }
    
    
    
    
    
        // PLAN-CONSTRAINT operationalRangeConstraint provenance=FROZEN_REQUIREMENT activation=ALWAYS verification=PARAMETRIC_SWEEP
        assert constraint operationalRangeConstraint {
            currentOperationalRange >= minOperationalRange
        }
    }

    part def PerceptionSystem {
        out port obstacleAvoidanceSeparation : ObstacleAvoidanceSeparationPort;
        out port attitudeDeviations : AttitudeDeviationsPort;
        out port cruiseAirspeed : CruiseAirspeedPort;
        out port forwardGroundSpeed : ForwardGroundSpeedPort;
        out port flightAltitude : FlightAltitudePort;
        out port sensorStatus : SensorStatusPort;
        inout port gnssCorrections : GnssCorrectionsPort;

        satisfy requirement REQ_INTF_002;

        action def ApplyGnssCorrectionsAction { }
    }

    part def CommunicationSystem {
        out port uplinkCommStatus : UplinkCommStatusPort;
        in port telemetryDataLink : TelemetryDataLinkPort;
        out port waypointNavigateCommand : WaypointNavigateCommandPort;
        out port waypointModification : WaypointModificationPort;
        in port landingHealthReport : LandingHealthReportPort;
        inout port rfLink : RfLinkPort;
        out port remoteId : RemoteIdPort;
        out port commStatus : CommStatusPort;

        satisfy requirement REQ_FUNC_004;
        satisfy requirement REQ_INTF_001;
        satisfy requirement REQ_INTF_003;

        action def MavlinkExchangeAction { }
        action def BroadcastRemoteIdAction { }
    }

part def PayloadMechanism {
        in port deliveryPayloadCmd : DeliveryPayloadCmdPort;
        in port abortLockCmd : AbortLockCmdPort;

        attribute maxPayloadReleaseLatency : Real = 2.0 [s];
        attribute measuredPayloadReleaseLatency : Real = 0.0 [s];
        attribute deliveryAbortConditionActive : Boolean = false;
        attribute isMechanicallyLocked : Boolean = true;

        satisfy requirement REQ_FUNC_005;
        satisfy requirement REQ_PERF_005;
        satisfy requirement REQ_SAFE_006;
        satisfy requirement REQ_SAFE_008;

        // PLAN-CONSTRAINT payloadReleaseLatencyConstraint provenance=FROZEN_REQUIREMENT activation=ALWAYS verification=STATE_EXECUTION
        assert constraint payloadReleaseLatencyConstraint {
            measuredPayloadReleaseLatency <= maxPayloadReleaseLatency
        }

        action def defaultToMechanicallyLockedState {}
        action def maintainMechanicallyLockedState {}
        action def releasePayload {}
        action def remainPoweredOff {}
        action def securePayload {}
        action def unlockPayload {}

                                state def PayloadReleaseBehavior {
            entry; then Locked;

            state Locked {
                do action runLocked : securePayload;
            }
            state Releasing {
                entry action onReleasing : releasePayload;
            }

            transition releaseConditionMet
                first Locked
                accept DeliveryCoordinateConditionSatisfied
                if not deliveryAbortConditionActive
                then Releasing;
        }
    
    
    
    
                                state def PayloadLockBehavior {
            entry; then Locked;

            state Locked {
                do action runLocked : maintainMechanicallyLockedState;
            }
            state Unlocked {
                entry action onUnlocked : unlockPayload;
            }

            transition unlockCommandReceived
                first Locked
                accept PayloadReleaseCommand
                if not deliveryAbortConditionActive
                then Unlocked;
        }
    
    
    
    
                                state def MechanicallyLockedInitializationBehavior {
            entry; then PowerOff;

            state PowerOff {
                do action runPowerOff : remainPoweredOff;
            }
            state MechanicallyLocked {
                entry action onMechanicallyLocked : defaultToMechanicallyLockedState;
            }

            transition powerOn
                first PowerOff
                accept PowerOn
                then MechanicallyLocked;
        }
    
    
    
    }

    part def PowerSystem {
        out port flightDuration : FlightDurationPort;
        out port operationalRange : OperationalRangePort;
        out port batteryStatus : BatteryStatusPort;

        satisfy requirement REQ_PERF_002;
        satisfy requirement REQ_PERF_006;
    }

part def SafetyMonitor {
        out port contingencyReturnLandingCmd : ContingencyReturnLandingCmdPort;
        in port uplinkCommStatus : UplinkCommStatusPort;
        in port sensorStatus : SensorStatusPort;
        in port batteryStatus : BatteryStatusPort;
        in port propulsionStatus : PropulsionStatusPort;
        out port recoveryCmd : RecoveryCmdPort;
        out port abortLockCmd : AbortLockCmdPort;
        out port overrideCmd : OverrideCmdPort;
        in port commStatus : CommStatusPort;

        attribute maxParachuteDeploymentLatency : Real = 0.5 [s];
        attribute measuredParachuteDeploymentLatency : Real = 0.0 [s];
        attribute batterySoc : Real = 100.0 [percent];
        attribute commLossTime : Real = 0.0 [s];
        attribute parachuteDeployTime : Real = 0.5 [s];
        attribute propulsionCriticalFailure : Boolean = false;
        attribute sensorSelfTestFailed : Boolean = false;
        attribute sensorFailureReported : Boolean = false;

        satisfy requirement REQ_SAFE_001;
        satisfy requirement REQ_SAFE_002;
        satisfy requirement REQ_SAFE_003;
        satisfy requirement REQ_SAFE_004;
        satisfy requirement REQ_SAFE_005;

        // PLAN-CONSTRAINT parachuteDeploymentLatencyConstraint provenance=FROZEN_REQUIREMENT activation=ALWAYS verification=STATE_EXECUTION
        assert constraint parachuteDeploymentLatencyConstraint {
            measuredParachuteDeploymentLatency <= maxParachuteDeploymentLatency
        }

        action def CMD_RTL { }
        action def CMD_LAND { }
        action def initiateBatteryRtb { 
            send CMD_RTL() to overrideCmd; 
        }
        action def initiateEmergencyLand { 
            send CMD_LAND() to overrideCmd; 
        }
        action def deployBallisticRecoveryParachute {
            send RecoveryCmdData() to recoveryCmd;
        }
        action def monitorPropulsionHealth {}
        action def performSelfTest {}
        action def transitionToArmedState {}

        state def BatteryRtbMonitor {
            state RtbNominal;
            state RtbDetected;
            entry; then RtbNominal;
            transition first RtbNominal
                if batterySoc <= 25.0
                then RtbDetected;
        }

        state def BatteryLandMonitor {
            state LandNominal;
            state LandDetected;
            entry; then LandNominal;
            transition first LandNominal
                if batterySoc < 15.0
                then LandDetected;
        }

        state def CommLossMonitor {
            state CommNominal;
            state CommLossDetected;
            entry; then CommNominal;
            transition first CommNominal
                if commLossTime > 10.0
                then CommLossDetected;
        }

        state def SafetyArbiter {
            state ArbNominal;
            state ArbParachuteMode {
                entry action onParachute : deployBallisticRecoveryParachute;
            }
            state ArbLandMode {
                entry action onLand : initiateEmergencyLand;
            }
            state ArbRtbMode {
                entry action onRtb : initiateBatteryRtb;
            }
            entry; then ArbNominal;
            transition first ArbNominal
                if propulsionCriticalFailure
                then ArbParachuteMode;
            transition first ArbNominal
                if batterySoc < 15.0
                and not propulsionCriticalFailure
                then ArbLandMode;
            transition first ArbNominal
                if commLossTime > 10.0
                and not propulsionCriticalFailure
                then ArbLandMode;
            transition first ArbNominal
                if batterySoc <= 25.0
                and batterySoc >= 15.0
                and commLossTime <= 10.0
                and not propulsionCriticalFailure
                then ArbRtbMode;
        }

                                state def ParachuteDeploymentBehavior {
            entry; then Monitoring;

            state Monitoring {
                do action runMonitoring : monitorPropulsionHealth;
            }
            state DeployingParachute {
                entry action onDeployingParachute : deployBallisticRecoveryParachute;
            }

            transition criticalFailureDetected
                first Monitoring
                accept CriticalPropulsionSubsystemFailure
                then DeployingParachute;
        }
    
    
    
    
                                state def ArmedStateInhibitionBehavior {
            entry; then PowerOnSelfTest;

            state PowerOnSelfTest {
                do action runPowerOnSelfTest : performSelfTest;
            }
            state Armed {
                entry action onArmed : transitionToArmedState;
            }

            transition armingCommandReceived
                first PowerOnSelfTest
                accept ArmingCommand
                if not sensorFailureReported
                then Armed;
        }
    
    
    
    }

    part def PropulsionSystem {
        in port propulsionCmd : PropulsionCmdPort;
        out port payloadThrottleMargin : PayloadThrottleMarginPort;
        out port propulsionStatus : PropulsionStatusPort;

        satisfy requirement REQ_SAFE_007;

        action def maintainControlledFlight {}
        action def operateAllMotors {}

                                                        state def PropulsionFaultToleranceBehavior {
            entry; then NominalOperation;

            state NominalOperation {
                do action runNominalOperation : operateAllMotors;
            }
            state SingleMotorFailure {
                do action runSingleMotorFailure : maintainControlledFlight;
            }

            transition motorFailureDetected
                first NominalOperation
                accept SinglePropulsionUnitFailure
                then SingleMotorFailure;
        }
    
    
    
    
    
    
    }

    part def RecoverySystem {
        in port recoveryCmd : RecoveryCmdPort;
    }

    part def Airframe {
        out port payloadMassProperties : PayloadMassPropertiesPort;

        satisfy requirement REQ_CONS_002;
        satisfy requirement REQ_CONS_003;
        satisfy requirement REQ_CONS_004;
    }

    // System Parts Instantiation
    part flightController : FlightController;
    part perceptionSystem : PerceptionSystem;
    part communicationSystem : CommunicationSystem;
    part payloadMechanism : PayloadMechanism;
    part powerSystem : PowerSystem;
    part safetyMonitor : SafetyMonitor;
    part propulsionSystem : PropulsionSystem;
    part recoverySystem : RecoverySystem;
    part airframe : Airframe;

    // Inter-component Data Flows
    connect perceptionSystem.obstacleAvoidanceSeparation to flightController.obstacleAvoidanceSeparation;
    connect propulsionSystem.payloadThrottleMargin to flightController.payloadThrottleMargin;
    connect perceptionSystem.attitudeDeviations to flightController.attitudeDeviations;
    connect powerSystem.flightDuration to flightController.flightDuration;
    connect perceptionSystem.cruiseAirspeed to flightController.cruiseAirspeed;
    connect perceptionSystem.forwardGroundSpeed to flightController.forwardGroundSpeed;
    connect powerSystem.operationalRange to flightController.operationalRange;
    connect perceptionSystem.flightAltitude to flightController.flightAltitude;
    connect airframe.payloadMassProperties to flightController.payloadMassProperties;
    connect safetyMonitor.contingencyReturnLandingCmd to flightController.contingencyReturnLandingCmd;
    connect communicationSystem.waypointNavigateCommand to flightController.waypointNavigateCommand;
    connect flightController.telemetryDataLink to communicationSystem.telemetryDataLink;
    connect flightController.deliveryPayloadCmd to payloadMechanism.deliveryPayloadCmd;
    connect flightController.propulsionCmd to propulsionSystem.propulsionCmd;
    connect communicationSystem.waypointModification to flightController.waypointModification;
    connect flightController.landingHealthReport to communicationSystem.landingHealthReport;
    connect safetyMonitor.overrideCmd to flightController.overrideCmd;

    connect communicationSystem.uplinkCommStatus to safetyMonitor.uplinkCommStatus;
    connect perceptionSystem.sensorStatus to safetyMonitor.sensorStatus;
    connect powerSystem.batteryStatus to safetyMonitor.batteryStatus;
    connect propulsionSystem.propulsionStatus to safetyMonitor.propulsionStatus;
    connect safetyMonitor.recoveryCmd to recoverySystem.recoveryCmd;
    connect safetyMonitor.abortLockCmd to payloadMechanism.abortLockCmd;
    connect communicationSystem.commStatus to safetyMonitor.commStatus;
}
